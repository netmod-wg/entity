module iana-entity {
  namespace "urn:ietf:params:xml:ns:yang:iana-entity";
  prefix ianaent;

  organization "IANA";
  contact
    "        Internet Assigned Numbers Authority

     Postal: ICANN
             4676 Admiralty Way, Suite 330
             Marina del Rey, CA 90292

     Tel:    +1 310 823 9358
     <mailto:iana@iana.org>";


  description
    "IANA defined identities for physical class.";
  reference
    "https://www.iana.org/assignments/ianaentity-mib/ianaentity-mib";

  // RFC Ed.: replace XXXX with actual RFC number and remove this
  // note.

  // RFC Ed.: update the date below with the date of RFC publication
  // and remove this note.
  revision 2016-10-25 {
    description
      "Initial revision.";
    reference
      "RFC XXXX: A YANG Data Model for hardware Management";
  }

  /*
   * Identities
   */

  identity entity-physical-class {
    description
      "This identity is the base for all physical entity class
       identifiers.";
  }


  identity unknown {
    base ianaent:entity-physical-class;
    description
      "This identity is applicable if the physical entity class
       is unknown to the server.";
  }

  identity chassis {
    base ianaent:entity-physical-class;
    description
      "This identity is applicable if the physical entity class
       is an overall container for networking equipment.  Any class
       of physical entity, except a stack, may be contained within a
       chassis; a chassis may only be contained within a stack.";
  }

  identity backplane {
    base ianaent:entity-physical-class;
    description
      "This identity is applicable if the physical entity class
       is some sort of device for aggregating and forwarding
       networking traffic, such as a shared backplane in a modular
       ethernet switch.  Note that an implementation may model a
       backplane as a single physical entity, which is actually
       implemented as multiple discrete physical components (within a
       chassis or stack).";
  }

  identity container {
    base ianaent:entity-physical-class;
    description
      "This identity is applicable if the physical entity class
       is capable of containing one or more removable physical
       entities, possibly of different types.  For example, each
       (empty or full) slot in a chassis will be modeled as a
       container.  Note that all removable physical entities should
       be modeled within a container entity, such as field-
       replaceable modules, fans, or power supplies.  Note that all
       known containers should be modeled by the agent, including
       empty containers.";
  }

  identity power-supply {
    base ianaent:entity-physical-class;
    description
      "This identity is applicable if the physical entity class
       is a power-supplying component.";
  }

  identity fan {
    base ianaent:entity-physical-class;
    description
      "This identity is applicable if the physical entity class
       is a fan or other heat-reduction component.";
  }

  identity sensor {
    base ianaent:entity-physical-class;
    description
      "This identity is applicable if the physical entity class
       is some sort of sensor, such as a temperature sensor within a
       router chassis.";
  }

  identity module {
    base ianaent:entity-physical-class;
    description
      "This identity is applicable if the physical entity class
       is some sort of self-contained sub-system.  If a 'module'
       entity is removable, then it should be modeled within a
       container entity; otherwise, it should be modeled directly
       within another physical entity (e.g., a chassis or another
       module).";
  }

  identity port {
    base ianaent:entity-physical-class;
    description
      "This identity is applicable if the physical entity class
       is some sort of networking port, capable of receiving and/or
       transmitting networking traffic.";
  }

  identity stack {
    base ianaent:entity-physical-class;
    description
      "This identity is applicable if the physical entity class
       is some sort of super-container (possibly virtual) intended to
       group together multiple chassis entities.  A stack may be
       realized by a 'virtual' cable, a real interconnect cable
       attached to multiple chassis, or multiple interconnect cables.
       A stack should not be modeled within any other physical
       entities, but a stack may be contained within another stack.
       Only chassis entities should be contained within a stack.";
  }

  identity cpu {
    base ianaent:entity-physical-class;
    description
      "This identity is applicable if the physical entity class
       is some sort of central processing unit.";
  }

  identity energy-object {
    base ianaent:entity-physical-class;
    description
      "This identity is applicable if the physical entity class
       is some sort of energy object, i.e., a piece of equipment that
       is part of or attached to a communications network that is
       monitored, controlled, or aids in the management of another
       device for Energy Management.";
  }

  identity battery {
    base ianaent:entity-physical-class;
    description
      "This identity is applicable if the physical entity class
       is some sort of battery.";
  }

  identity storage-drive {
    base ianaent:entity-physical-class;
    description
      "This identity is applicable if the physical entity class
       is some sort of entity with data storage capability as main
       functionality, e.g., disk drive (HDD), solid state device
       (SSD), hybrid (SSHD), object storage (OSD) or other.";
  }
}
