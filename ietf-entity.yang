module ietf-entity {
  yang-version 1.1;
  namespace "urn:ietf:params:xml:ns:yang:ietf-entity";
  prefix ent;

  import ietf-inet-types {
    prefix inet;
  }
  import ietf-yang-types {
    prefix yang;
  }
  import iana-entity {
    prefix ianaent;
  }

  organization
    "IETF NETMOD (NETCONF Data Modeling Language) Working Group";

  contact
    "WG Web:   <http://tools.ietf.org/wg/netmod/>
     WG List:  <mailto:netmod@ietf.org>

     WG Chair: Lou Berger
               <mailto:lberger@labn.net>

     WG Chair: Juergen Schoenwaelder
               <mailto:j.schoenwaelder@jacobs-university.de>

     WG Chair: Kent Watsen
               <mailto:kwatsen@juniper.net>

     Editor:   Andy Bierman
               <mailto:andy@yumaworks.com>

     Editor:   Martin Bjorklund
               <mailto:mbj@tail-f.com>

     Editor:   Jie Dong
               <mailto:jie.dong@huawei.com>

     Editor:   Dan Romascanu
               <mailto:dromasca@avaya.com>";

  // RFC Ed.: replace XXXX with actual RFC number and remove this
  // note.

  description
    "This module contains a collection of YANG definitions for
     managing physical entities.

     Copyright (c) 2016 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: update the date below with the date of RFC publication
  // and remove this note.
  revision 2016-08-26 {
    description
      "Initial revision.";
    reference
      "RFC XXXX: A YANG Data Model for Entity Management";
  }

  /*
   * Features
   */

  feature entity-mib {
    description
      "This feature indicates that the device implements
       the ENTITY-MIB.";
    reference "RFC 6933: Entity MIB (Version 4)";
  }

  feature entity-config {
    description
      "Indicates that the server supports configuration of
       physical entities.";
  }

  feature entity-state {
    description
      "Indicates the ENTITY-STATE-MIB objects are supported";
    reference "RFC 4268: Entity State MIB";
  }

  feature entity-sensor {
    description
      "Indicates the ENTITY-SENSOR-MIB objects are supported";
    reference "RFC 3433: Entity Sensor MIB";
  }

  /*
   * Typedefs
   */

  typedef entity-admin-state {
    type enumeration {
      enum unknown {
        value 1;
        description
          "The resource is unable to report administrative state.";
      }
      enum locked {
        value 2;
        description
          "The resource is administratively prohibited from use.";
      }
      enum shutting-down {
        value 3;
        description
          "The resource usage is administratively limited to current
           instances of use.";
      }
      enum unlocked {
        value 4;
        description
          "The resource is not administratively prohibited from use.";
      }
    }
    description
      "Represents the various possible administrative states.";
    reference "RFC 4268: EntityAdminState";
  }

  typedef entity-oper-state {
    type enumeration {
      enum unknown {
        value 1;
        description
          "The resource is unable to report operational state.";
      }
      enum disabled {
        value 2;
        description
          "The resource is totally inoperable.";
      }
      enum enabled {
        value 3;
        description
          "The resource is partially or fully operable.";
      }
      enum testing {
        value 4;
        description
          "The resource is currently being tested and cannot
           therefore report whether it is operational or not.";
      }
    }
    description
      "Represents the possible values of operational states.";
    reference "RFC 4268: EntityOperState";
  }

  typedef entity-usage-state {
    type enumeration {
      enum unknown {
        value 1;
        description
          "The resource is unable to report usage state.";
      }
      enum idle {
        value 2;
        description
          "The resource is servicing no users.";
      }
      enum active {
        value 3;
        description
          "The resource is currently in use and it has sufficient
           spare capacity to provide for additional users.";
      }
      enum busy {
        value 4;
        description
          "The resource is currently in use, but it currently has
           no spare capacity to provide for additional users.";
      }
    }
    description
      "Represents the possible values of usage states.";
    reference "RFC 4268, EntityUsageState";
  }

  typedef entity-alarm-status {
    type bits {
      bit unknown {
        position 0;
        description
          "The resource is unable to report alarm state.";
      }
      bit under-repair {
        position 1;
        description
          "The resource is currently being repaired, which, depending
           on the implementation, may make the other values in this
           bit string not meaningful.";
      }
      bit critical {
        position 2;
        description
          "One or more critical alarms are active against the
           resource.";
      }
      bit major {
        position 3;
        description
          "One or more major alarms are active against the resource.";
      }
      bit minor {
        position 4;
        description
          "One or more minor alarms are active against the resource.";
      }
      bit warning {
        position 5;
        description
          "One or more warning alarms are active against the resource.
           This alarm status is not defined in X.733.";
      }
      bit indeterminate {
        position 6;
        description
          "One or more alarms of whose perceived severity cannot be
           determined are active against this resource.
           This alarm status is not defined in X.733.";
      }
    }
    description
      "Represents the possible values of alarm status.
       An Alarm [RFC3877] is a persistent indication of an error or
       warning condition.

       When no bits of this attribute are set, then no active
       alarms are known against this entity and it is not under
       repair.";
    reference "RFC 4268: EntityAlarmStatus";
  }

  typedef entity-standby-status {
    type enumeration {
      enum unknown {
        value 1;
        description
          "The resource is unable to report standby state.";
      }
      enum hot-standby {
        value 2;
        description
          "The resource is not providing service, but it will be
           immediately able to take over the role of the resource
           to be backed up, without the need for initialization
           activity, and will contain the same information as the
           resource to be backed up.";
      }
      enum cold-standby {
        value 3;
        description
          "The resource is to back up another resource, but will not
           be immediately able to take over the role of a resource
           to be backed up, and will require some initialization
           activity.";
      }
      enum providing-service {
        value 4;
        description
          "The resource is providing service.";
      }
    }
    description
      "Represents the possible values of standby status.";
    reference "RFC 4268: EntityStandbyStatus";
  }

  typedef entity-sensor-data-type {
    type enumeration {
      enum other {
        value 1;
        description
          "A measure other than those listed below.";
      }
      enum unknown {
        value 2;
        description
          "An unknown measurement, or arbitrary, relative numbers";
      }
      enum volts-AC {
        value 3;
        description
          "A measure of electric potential (alternating current).";
      }
      enum volts-DC {
        value 4;
        description
          "A measure of electric potential (direct current).";
      }
      enum amperes {
        value 5;
        description
          "A measure of electric current.";
      }
      enum watts {
        value 6;
        description
          "A measure of power.";
      }
      enum hertz {
        value 7;
        description
          "A measure of frequency.";
      }
      enum celsius {
        value 8;
        description
          "A measure of temperature.";
      }
      enum percent-RH {
        value 9;
        description
          "A measure of percent relative humidity.";
      }
      enum rpm {
        value 10;
        description
          "A measure of shaft revolutions per minute.";
      }
      enum cmm {
        value 11;
        description
          "A measure of cubic meters per minute (airflow).";
      }
      enum truth-value {
        value 12;
        description
          "Value is one of 1 (true) or 2 (false)";
      }
    }
    description
      "An node using this data type represents the Entity Sensor
       measurement data type associated with a physical sensor
       value. The actual data units are determined by examining an
       node of this type together with the associated
       entity-sensor-data-scale node.

       An node of this type SHOULD be defined together with nodes
       of type entity-sensor-data-scale and
       entity-sensor-precision. These three types are used to
       identify the semantics of an node of type
       entity-sensor-value.";
    reference "RFC 3433: EntitySensorDataType";
  }

  typedef entity-sensor-data-scale {
    type enumeration {
      enum yocto {
        value 1;
        description
          "Data scaling factor of 10^-24.";
      }
      enum zepto {
        value 2;
        description
          "Data scaling factor of 10^-21.";
      }
      enum atto {
        value 3;
        description
          "Data scaling factor of 10^-18.";
      }
      enum femto {
        value 4;
        description
          "Data scaling factor of 10^-15.";
      }
      enum pico {
        value 5;
        description
          "Data scaling factor of 10^-12.";
      }
      enum nano {
        value 6;
        description
          "Data scaling factor of 10^-9.";
      }
      enum micro {
        value 7;
        description
          "Data scaling factor of 10^-6.";
      }
      enum milli {
        value 8;
        description
          "Data scaling factor of 10^-3.";
      }
      enum units {
        value 9;
        description
          "Data scaling factor of 10^0.";
      }
      enum kilo {
        value 10;
        description
          "Data scaling factor of 10^3.";
      }
      enum mega {
        value 11;
        description
          "Data scaling factor of 10^6.";
      }
      enum giga {
        value 12;
        description
          "Data scaling factor of 10^9.";
      }
      enum tera {
        value 13;
        description
          "Data scaling factor of 10^12.";
      }
      enum exa {
        value 14;
        description
          "Data scaling factor of 10^15.";
      }
      enum peta {
        value 15;
        description
          "Data scaling factor of 10^18.";
      }
      enum zetta {
        value 16;
        description
          "Data scaling factor of 10^21.";
      }
      enum yotta {
        value 17;
        description
          "Data scaling factor of 10^24.";
      }
    }
    description
      "An node using this data type represents a data scaling
       factor, represented with an International System of Units (SI)
       prefix.  The actual data units are determined by examining an
       node of this type together with the associated
       entity-sensor-data-type.

       An node of this type SHOULD be defined together with nodes
       of type entity-sensor-data-type and entity-sensor-precision.
       Together, associated nodes of these three types are used to
       identify the semantics of an node of type
       entity-sensor-value.";
    reference "RFC 3433: EntitySensorDataScale";
  }

  typedef entity-sensor-precision {
    type int32 {
      range "-8 .. 9";
    }
    description
      "An node using this data type represents a sensor
       precision range.

       An node of this type SHOULD be defined together with nodes
       of type entity-sensor-data-type and entity-sensor-data-scale.
       Together, associated nodes of these three types are used to
       identify the semantics of an node of type
       entity-sensor-value.

       If an node of this type contains a value in the range 1 to 9,
       it represents the number of decimal places in the fractional
       part of an associated entity-sensor-value fixed- point number.

       If an node of this type contains a value in the range -8 to
       -1, it represents the number of accurate digits in the
       associated entity-sensor-value fixed-point number.

       The value zero indicates the associated entity-sensor-value
       node is not a fixed-point number.

       Server implementors must choose a value for the associated
       entity-sensor-precision node so that the precision and
       accuracy of the associated entity-sensor-value node is
       correctly indicated.

       For example, a physical entity representing a temperature
       sensor that can measure 0 degrees to 100 degrees C in 0.1
       degree increments, +/- 0.05 degrees, would have an
       entity-sensor-precision value of '1', an
       entity-sensor-data-scale value of 'units', and an
       entity-sensor-value ranging from '0' to '1000'.  The
       entity-sensor-value would be interpreted as 'degrees C * 10'.";
    reference "RFC 3433: EntitySensorPrecision";
  }

  typedef entity-sensor-value {
    type int32 {
      range "-1000000000 .. 1000000000";
    }
    description
     "An node using this data type represents an Entity Sensor
      value.

      An node of this type SHOULD be defined together with nodes
      of type entity-sensor-data-type, entity-sensor-data-scale, and
      entity-sensor-precision.  Together, associated nodes of those
      three types are used to identify the semantics of an node of
      this data type.

      The semantics of an node using this data type are determined
      by the value of the associated entity-sensor-data-type node.

      If the associated entity-sensor-data-type node is equal to
      'voltsAC', 'voltsDC', 'amperes', 'watts', 'hertz',
      'celsius', or 'cmm', then an node of this type MUST
      contain a fixed point number ranging from -999,999,999 to
      +999,999,999.  The value -1000000000 indicates an underflow
      error. The value +1000000000 indicates an overflow error.  The
      entity-sensor-precision indicates how many fractional digits
      are represented in the associated entity-sensor-value node.

      If the associated entity-sensor-data-type node is equal to
      'percentRH', then an node of this type MUST contain a
      number ranging from 0 to 100.

      If the associated entity-sensor-data-type node is equal to
      'rpm', then an node of this type MUST contain a number
      ranging from -999,999,999 to +999,999,999.

      If the associated entity-sensor-data-type node is equal to
      'truthvalue', then an node of this type MUST contain
      either the value 1 (true) or the value 2 (false)'.

      If the associated entity-sensor-data-type node is equal to
      'other' or unknown', then an node of this type MUST
      contain a number ranging from -1000000000 to 1000000000.";
    reference "RFC 3433: EntitySensorValue";
  }

  typedef entity-sensor-status {
    type enumeration {
      enum ok {
        value 1;
        description
          "Indicates that the server can obtain the sensor value.";
      }
      enum unavailable {
        value 2;
        description
          "Indicates that the server presently cannot obtain the
           sensor value.";
      }
      enum nonoperational {
        value 3;
        description
          "Indicates that the server believes the sensor is broken.
           The sensor could have a hard failure (disconnected wire),
           or a soft failure such as out-of-range, jittery, or wildly
           fluctuating readings.";
      }
    }
    description
      "An node using this data type represents the operational
       status of a physical sensor.";
    reference "RFC 3433: EntitySensorStatus";
  }

  /*
   * Operational state data nodes
   */

  container entity-state {
    config false;
    description
      "Data nodes for the operational state of physical entities.";

    leaf last-change {
      type yang:date-and-time;
      description
        "The time the '/entity-state/physical-entity' list changed.";
    }

    list physical-entity {
      key name;
      description
        "List of physical entities";
      reference "RFC 6933: entPhysicalEntry";

      leaf name {
        type string;
        description
          "Administrative name assigned to this physical entity.
           No restrictions apply. Not required to be the same as
           entPhysicalName.";
      }

      leaf class {
        type identityref {
          base ianaent:entity-physical-class;
        }
        mandatory true;
        description
          "An indication of the general hardware type
           of the physical entity.";
        reference "RFC 6933: entPhysicalClass";
      }

      leaf physical-index {
        if-feature entity-mib;
        type int32 {
          range "1..2147483647";
        }
        description
          "The entPhysicalIndex for the entPhysicalEntry represented
           by this list entry.";
        reference "RFC 6933: entPhysicalIndex";
      }

      leaf description {
        type string;
        description
          "A textual description of physical entity.  This node
           should contain a string that identifies the manufacturer's
           name for the physical entity and should be set to a
           distinct value for each version or model of the physical
           entity.";
        reference "RFC 6933: entPhysicalDescr";
      }

      leaf-list contained-in {
        type leafref {
          path "../../physical-entity/name";
        }
        description
          "The name of the physical entity that 'contains'
           this physical entity.";
        reference "RFC 6933: entPhysicalContainedIn";
      }

      leaf-list contains-child {
        type leafref {
          path "../../physical-entity/name";
        }
        description
          "The name of the contained physical entity.";
        reference "RFC 6933: entPhysicalChildIndex";
      }

      leaf parent-rel-pos {
        type int32 {
          range "0 .. 2147483647";
        }
        description
          "An indication of the relative position of this child
           component among all its sibling components.  Sibling
           components are defined as physical entities that share the
           same instance values of each of the contained-in
           and class elements.";
        reference "RFC 6933: entPhysicalParentRelPos";
      }

      leaf hardware-rev {
        type string;
        description
          "The vendor-specific hardware revision string for the
           physical entity.  The preferred value is the hardware
           revision identifier actually printed on the component
           itself (if present).";
        reference "RFC 6933: entPhysicalHardwareRev";
      }

      leaf firmware-rev {
        type string;
        description
          "The vendor-specific firmware revision string for the
           physical entity.";
        reference "RFC 6933: entPhysicalFirmwareRev";
      }

      leaf software-rev {
        type string;
        description
          "The vendor-specific software revision string for the
           physical entity.";
        reference "RFC 6933: entPhysicalSoftwareRev";
      }

      leaf serial-num {
        type string;
        description
          "The vendor-specific serial number string for the physical
           entity.  The preferred value is the serial number string
           actually printed on the component itself (if present).

           If a serial number has been configured for this entity in
           /entity/physical-entity/serial-num, this node contains the
           configured value.";
        reference "RFC 6933: entPhysicalSerialNum";
      }

      leaf mfg-name {
        type string;
        description
          "The name of the manufacturer of this physical component.
           The preferred value is the manufacturer name string
           actually printed on the component itself (if present).

           Note that comparisons between instances of the model-name,
           firmware-rev, software-rev, and the serial-num nodes are
           only meaningful amongst physical entities with the same
           value of mfg-name.

           If the manufacturer name string associated with the
           physical component is unknown to the server, then this
           node will contain a zero-length string.";
        reference "RFC 6933: entPhysicalMfgName";
      }

      leaf model-name {
        type string;
        description
          "The vendor-specific model name identifier string associated
           with this physical component.  The preferred value is the
           customer-visible part number, which may be printed on the
           component itself.

           If the model name string associated with the physical
           component is unknown to the server, then this node will
           contain a zero-length string.";
        reference "RFC 6933: entPhysicalModelName";
      }

      leaf alias {
        type string {
          length "0 .. 32";
        }
        description
          "An 'alias' name for the physical entity, as specified by
           a network manager, and provides a non-volatile 'handle'
           for the physical entity.

           If an alias has been configured for this entity in
           /entity/physical-entity/alias, this node contains the
           configured value.  If no such alias has been configured,
           the server may set the value of this node to a locally
           unique value.";
        reference "RFC 6933: entPhysicalAlias";
      }

      leaf asset-id {
        type string {
          length "0 .. 32";
        }
        description
          "This node is a user-assigned asset tracking identifier
           (as specified by a network manager) for the physical entity
           and provides non-volatile storage of this information.

           If an asset tracking identifier has been configured for
           this entity in /entity/physical-entity/addet-id, this node
           contains the configured value.";
        reference "RFC 6933: entPhysicalAssetID";
      }

      leaf is-fru {
        type boolean;
        description
          "This node indicates whether or not this physical entity
           is considered a 'field replaceable unit' by the vendor.  If
           this node contains the value 'true', then this
           physical entity identifies a field replaceable unit.  For
           all physical entities that represent components permanently
           contained within a field replaceable unit, the value
           'false' should be returned for this node.";
        reference "RFC 6933: entPhysicalIsFRU";
      }

      leaf mfg-date {
        type yang:date-and-time;
        description
          "The date of manufacturing of the managed entity.";
        reference "RFC 6933: entPhysicalMfgDate";
      }

      leaf-list uri {
        type inet:uri;
        description
          "This node contains identification information about the
           physical entity.

           If uris have been configured for this entity in
           /entity/physical-entity/uri, this node contains the
           configured values.";
        reference "RFC 6933: entPhysicalUris";
      }

      leaf uuid {
        type yang:uuid;
        description
          "A Universally Unique Identifier of the physical entity.";
        reference "RFC 6933: entPhysicalUUID";
      }

      container state {
        if-feature entity-state;
        description
          "State-related nodes";
        reference "RFC 4268: Entity State MIB";

        leaf state-last-changed {
          type yang:date-and-time;
          description
            "The date and time when the value of any of the
             admin-state, oper-state, usage-state, alarm-status, or
             standby-status changed for this entity.

             If there has been no change since the last
             re-initialization of the local system, this node contains
             the date and time of local system initialization.  If
             there has been no change since the entity was added to
             the local system, this node contains the date and time of
             the insertion.";
          reference "RFC 4268: entStateLastChanged";
        }

        leaf admin-state {
          type entity-admin-state;
          description
            "The administrative state for this entity.

             This node refers to an entities administrative permission
             to service both other entities within its containment
             hierarchy as well other users of its services defined by
             means outside the scope of this module.

             Some physical entities exhibit only a subset of the
             remaining administrative state values.  Some entities
             cannot be locked, and hence this node exhibits only the
             'unlocked' state.  Other entities cannot be shutdown
             gracefully, and hence this node does not exhibit the
             'shutting-down' state.";
          reference "RFC 4268: entStateAdmin";
        }

        leaf oper-state {
          type entity-oper-state;
          description
            "The operational state for this entity.

             Note that this node does not follow the administrative
             state.  An administrative state of down does not predict
             an operational state of disabled.

             Note that some implementations may not be able to
             accurately report oper-state while the admin-state node
             has a value other than 'unlocked'.  In these cases, this
             node MUST have a value of 'unknown'.";
          reference "RFC 4268: entStateOper";
        }

        leaf usage-state {
          type entity-usage-state;
          description
            "The usage state for this entity.

             This node refers to an entity's ability to service more
             physical entities in a containment hierarchy.

             Some entities will exhibit only a subset of the usage
             state values.  Entities that are unable to ever service
             any entities within a containment hierarchy will always
             have a usage state of 'busy'.  Some entities will only
             ever be able to support one entity within its containment
             hierarchy and will therefore only exhibit values of
             'idle' and 'busy'.";
          reference "RFC 4268, entStateUsage";
        }

        leaf alarm-status {
          type entity-alarm-status;
          description
            "The alarm status for this entity.  It does not include
             the alarms raised on child components within its
             containment hierarchy.";
          reference "RFC 4268: entStateAlarm";
        }

        leaf standby-status {
          type entity-standby-status;
          description
            "The standby status for this entity.

             Some entities will exhibit only a subset of the
             remaining standby state values.  If this entity
             cannot operate in a standby role, the value of this
             node will always be 'providing-service'.";
          reference "RFC 4268: entStateStandby";
        }
      }

      container sensor-data {
        when 'derived-from-or-self(../class,
                                   "ianaent:sensor")' {
          description
            "Sensor data nodes present for any entity of type
             'sensor'";
        }
        if-feature entity-sensor;
        description
          "Sensor-related nodes.";
        reference "RFC 3433: Entity Sensor MIB";

        leaf data-type {
          type entity-sensor-data-type;
          description
            "The type of data units associated with the
             sensor value";
          reference "RFC 3433: entPhySensorType";
        }

        leaf data-scale {
          type entity-sensor-data-scale;
          description
            "The (power of 10) scaling factor associated
             with the sensor value";
          reference "RFC 3433: entPhySensorScale";
        }

        leaf precision {
          type entity-sensor-precision;
          description
            "The number of decimal places of precision
             associated with the sensor value";
          reference "RFC 3433: entPhySensorPrecision";
        }

        leaf value {
          type entity-sensor-value;
          description
            "The most recent measurement obtained by the server
             for this sensor.";
          reference "RFC 3433: entPhySensorValue";
        }

        leaf oper-status {
          type entity-sensor-status;
          description
            "The operational status of the sensor.";
          reference "RFC 3433: entPhySensorOperStatus";
        }

        leaf sensor-units-display {
          type string;
          description
            "A textual description of the data units that should be
             used in the display of the sensor value.";
          reference "RFC 3433: entPhySensorUnitsDisplay";
        }

        leaf value-timestamp {
          type yang:date-and-time;
          description
            "The time the status and/or value of this sensor was
             last obtained by the server.";
          reference "RFC 3433: entPhySensorValueTimeStamp";
        }

        leaf value-update-rate {
          type uint32;
          units "milliseconds";
          description
            "An indication of the frequency that the server updates
             the associated 'value' node, representing in
             milliseconds.  The value zero indicates:

              - the sensor value is updated on demand (e.g.,
                when polled by the server for a get-request),
              - the sensor value is updated when the sensor
                value changes (event-driven),
              - the server does not know the update rate.";
          reference "RFC 3433: entPhySensorValueUpdateRate";
        }
      }
    }
  }

  /*
   * Configuration data nodes
   */

  container entity {
    if-feature entity-config;
    description
      "Configuration parameters for physical entities.";

    list physical-entity {
      key name;
      description
        "List of configuration data for physical entities.";

      leaf name {
        type string;
        description
          "Administrative name assigned to this physical entity.
           No restrictions apply.";
      }

      leaf serial-num {
        type string;
        description
          "The vendor-specific serial number string for the physical
           entity.  The preferred value is the serial number string
           actually printed on the component itself (if present).

           This node is indented to be used for physical entities
           for which the server cannot determine the serial number.";
        reference "RFC 6933: entPhysicalSerialNum";
      }

      leaf alias {
        type string {
          length "0 .. 32";
        }
        description
          "This node is an 'alias' name for the physical entity, as
           specified by a network manager, and provides a non-volatile
           'handle' for the physical entity.";
        reference "RFC 6933: entPhysicalAlias";
      }

      leaf asset-id {
        type string {
          length "0 .. 32";
        }
        description
          "This node is a user-assigned asset tracking identifier
           (as specified by a network manager) for the physical
           entity";
        reference "RFC 6933: entPhysicalAssetID";
      }

      leaf-list uri {
        type inet:uri;
        description
          "This node contains identification information about the
           physical entity.";
        reference "RFC 6933: entPhysicalUris";
      }

      leaf admin-state {
        if-feature entity-state;
        type entity-admin-state;
        description
          "The administrative state for this entity.

           This node refers to an entity's administrative
           permission to service both other entities within
           its containment hierarchy as well other users of
           its services defined by means outside the scope
           of this module.

           Some physical entities exhibit only a subset of the
           remaining administrative state values.  Some entities
           cannot be locked, and hence this node exhibits only
           the 'unlocked' state.  Other entities cannot be shutdown
           gracefully, and hence this node does not exhibit the
           'shutting-down' state.";
        reference "RFC 4268, entStateAdmin";
      }
    }
  }

  /*
   * Notifications
   */

  notification ent-config-change {
    description
      "An ent-config-change notification is generated when the value
       of /entity-state/last-change changes.";
    reference "RFC 6933, entConfigChange";
  }

  notification ent-state-oper-enabled {
    if-feature entity-state;
    description
      "An ent-state-oper-enabled notification signifies that
       an entity has transitioned into the 'enabled' state.";

    leaf name {
      type leafref {
        path "/entity-state/physical-entity/name";
      }
      description
        "The name of the entity that has transitioned into the
         'enabled' state.";
    }
    leaf admin-state {
      type leafref {
        path "/entity-state/physical-entity/state/admin-state";
      }
      description
        "The administrative state for the entity.";
    }
    leaf alarm-status {
      type leafref {
        path "/entity-state/physical-entity/state/alarm-status";
      }
      description
        "The alarm status for the entity.";
    }
    reference "RFC 4268, entStateOperEnabled";
  }

  notification ent-state-oper-disabled {
    if-feature entity-state;
    description
      "An ent-state-oper-disabled notification signifies that
       an entity has transitioned into the 'disabled' state.";

    leaf name {
      type leafref {
        path "/entity-state/physical-entity/name";
      }
      description
        "The name of the entity that has transitioned into the
         'disabled' state.";
    }
    leaf admin-state {
      type leafref {
        path "/entity-state/physical-entity/state/admin-state";
      }
      description
        "The administrative state for the entity.";
    }
    leaf alarm-status {
      type leafref {
        path "/entity-state/physical-entity/state/alarm-status";
      }
      description
        "The alarm status for the entity.";
    }
    reference "RFC 4268, entStateOperDisabled";
  }

}
